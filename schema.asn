Configuration-Structure-Schema DEFINITIONS AUTOMATIC TAGS ::= BEGIN

   -- 2-bit integer
   Integer2 ::= INTEGER (0..3)

   -- 3-bit integer
   Integer3 ::= INTEGER (0..7)

   -- 4-bit integer
   Integer4 ::= INTEGER (0..15)

   -- 2-bit integer of range [0..3]
   Range2 ::= SEQUENCE {
      start Integer2,
      length Integer2
   }
   -- 3-bit integer of range [0..7]
   Range3 ::= SEQUENCE {
      start Integer3,
      length Integer3
   }
   -- 4-bit integer of range [0..15]
   Range4 ::= SEQUENCE {
      start Integer4,
      length Integer4
   }
   -- Any size of interger
   Range ::= SEQUENCE {
      start INTEGER,
      length INTEGER
   }

   -- 2-bit flexible range [0..3]
   FlexibleRange4 ::= SEQUENCE {
      -- The count of single sequence [1..4] which is
      -- a 2-bit count
      single SEQUENCE SIZE(1..4) OF Integer2 OPTIONAL,
      -- The intenger range is [0..3]
      range SEQUENCE OF Range2 OPTIONAL
   }

   -- 3-bit flexible range [0..7]
   FlexibleRange8 ::= SEQUENCE {
      -- The count of single sequence [1..8] which is 
      -- a 3-bit count
      single SEQUENCE SIZE(1..8) OF Integer3 OPTIONAL,
      -- The intenger range is [0..7]
      range SEQUENCE OF Range3 OPTIONAL
   }

   -- 4-bit flexible range [0..15]
   FlexibleRange16 ::= SEQUENCE {
      -- The count of single sequence [1..16] which is
      -- a 4-bit count
      single SEQUENCE SIZE(1..16) OF Integer3 OPTIONAL,
      -- The intenger range is [0..15]
      range SEQUENCE OF Range4 OPTIONAL
   }
   -- Any size of flexible range
   FlexibleRange ::= SEQUENCE {
      single SEQUENCE OF INTEGER OPTIONAL,
      range SEQUENCE OF Range OPTIONAL
   }
   HartExtension ::= CHOICE {
         debug Debug,
         isa Isa,
         privileged Privileged,
         clic Clic,
         fastInt FastInt,
         ...
   }
   Hart ::= SEQUENCE {
      hartid CHOICE { /* 4 choices use 2-bit as the index*/
        hartId4  FlexibleRange4, /* For hart number [1..4] */
        hartId8  FlexibleRange8, /* For hart number [1..8] */
        hartId16 FlexibleRange8, /* For hart number [1..16] */
        hartId   FlexibleRange   /* For hart number > 16 */
      },
      extension SEQUENCE OF HartExtension OPTIONAL,
      ...
   }
   Tuple ::= SEQUENCE {
      value INTEGER,
      mask INTEGER
   }
   Triple ::= SEQUENCE {
      low INTEGER,
      high INTEGER,
      mask INTEGER
   }
   PossibleValues ::= SEQUENCE {
      tuple SEQUENCE OF Tuple OPTIONAL,
      triple SEQUENCE OF Triple OPTIONAL,
      ...
   }
   Configuration ::= SEQUENCE {
      harts SEQUENCE OF Hart OPTIONAL,
      debugModule SEQUENCE OF DebugModule OPTIONAL,
      traceModule TraceModule OPTIONAL,
      physicalMemory SEQUENCE OF PhysicalMemory OPTIONAL,
      ...
   }
   DebugTriggerMcontrol ::= SEQUENCE {
      maskmax INTEGER,
      hit BOOLEAN,
      addressMatch BOOLEAN,
      dataMatch BOOLEAN,
      timingBefore BOOLEAN,
      timingAfter BOOLEAN,
      sizeAny BOOLEAN,
      sizeS8 BOOLEAN,
      sizeS16 BOOLEAN,
      sizeS32 BOOLEAN,
      sizeS64 BOOLEAN,
      sizeS80 BOOLEAN,
      sizeS96 BOOLEAN,
      sizeS112 BOOLEAN,
      sizeS128 BOOLEAN,
      actionMmode BOOLEAN,
      actionDmode BOOLEAN,
      chain BOOLEAN,
      matchEqual BOOLEAN,
      matchNapot BOOLEAN,
      matchGreaterEqual BOOLEAN,
      matchLess BOOLEAN,
      matchLowMask BOOLEAN,
      matchHighMask BOOLEAN,
      matchNotEqual BOOLEAN,
      matchNotNapot BOOLEAN,
      matchNotLowMask BOOLEAN,
      matchNotHighMask BOOLEAN,
      m BOOLEAN,
      s BOOLEAN,
      u BOOLEAN,
      execute BOOLEAN,
      store BOOLEAN,
      load BOOLEAN
   }
   DebugTrigger ::= SEQUENCE {
      index FlexibleRange,
      mcontrol SEQUENCE OF DebugTriggerMcontrol OPTIONAL,
      ...
   }
   AccessRegisterCommand ::= SEQUENCE {
      aarsize32 BOOLEAN,
      aarsize64 BOOLEAN,
      aarsize128 BOOLEAN,
      aarpostincrementSupported BOOLEAN,
      postexecSupported BOOLEAN,
      regno FlexibleRange
   }
   AccessMemoryCommand ::= SEQUENCE {
      aamvirtual0 BOOLEAN,
      aamvirtual1 BOOLEAN,
      aamsize8 BOOLEAN,
      aamsize16 BOOLEAN,
      aamsize32 BOOLEAN,
      aamsize64 BOOLEAN,
      aamsize128 BOOLEAN,
      aampostincrementSupported BOOLEAN,
      writeSupported BOOLEAN,
      readSupported BOOLEAN
   }
   AbstractCommand ::= SEQUENCE {
      accessRegister SEQUENCE OF AccessRegisterCommand OPTIONAL,
      quickAccess SEQUENCE OF BOOLEAN OPTIONAL,
      accessMemory SEQUENCE OF AccessMemoryCommand OPTIONAL,
      ...
   }
   DebugModule ::= SEQUENCE {
      index INTEGER OPTIONAL,
      abstract AbstractCommand OPTIONAL,
      connectedHarts FlexibleRange OPTIONAL,
      ...
   }
   Debug ::= SEQUENCE {
      trigger SEQUENCE OF DebugTrigger OPTIONAL,
      ...
   }
   Isa ::= SEQUENCE {
      riscv32 BOOLEAN OPTIONAL,
      riscv64 BOOLEAN OPTIONAL,
      riscv128 BOOLEAN OPTIONAL,
      ...
   }
   PrivModes ::= SEQUENCE {
      u BOOLEAN,
      m BOOLEAN,
      s BOOLEAN
   }
   PrivSatps ::= SEQUENCE {
      sv32 BOOLEAN,
      sv39 BOOLEAN,
      sv48 BOOLEAN,
      sv57 BOOLEAN,
      sv64 BOOLEAN
   }
   Privileged ::= SEQUENCE {
      modes PrivModes OPTIONAL,
      satps PrivSatps OPTIONAL,
      epmp BOOLEAN OPTIONAL,
      ...
   }
   Clic ::= SEQUENCE {
      mTimeRegisterAddress INTEGER OPTIONAL,
      mTimeCompareRegisterAddress INTEGER OPTIONAL,
      ...
   }
   FastInterruptModule ::= SEQUENCE {
      index SEQUENCE OF Range OPTIONAL,
      connectedHarts SEQUENCE OF Range OPTIONAL,
      ...
   }
   TraceModule ::= SEQUENCE {
      branchPredictorEntries INTEGER OPTIONAL,
      jumpTargetCacheEntries INTEGER OPTIONAL,
      contextBusWidth INTEGER OPTIONAL,
      ...
   }
   PhysicalMemory ::= SEQUENCE {
      address SEQUENCE OF Range,
      cacheable BOOLEAN OPTIONAL,
      lrScSupported BOOLEAN OPTIONAL,
      ...
   }
   FastInt ::= SEQUENCE {
      mModeTimeRegAddr INTEGER OPTIONAL,
      mModeTimeCompRegAddr INTEGER OPTIONAL,
      ...
   }
END
